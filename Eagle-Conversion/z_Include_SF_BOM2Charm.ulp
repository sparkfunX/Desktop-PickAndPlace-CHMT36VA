// Things to add: (equivalent to...)
/*

string pnpBasefile = B.name;
string 	  defaultFileLocation


*/


/** 
 * Process all information and create the output file
 */
void writeOutputFile(int layer, string prefix) {
  string fileName = filesetext(pnpBasefile, prefix + ".dpv");

  if(defaultFileLocation != "")
  {
    fileName = defaultFileLocation + filesetext(filename(pnpBasefile), prefix + ".dpv");
  }

  //Prompt user for location to store file
  fileName = dlgFileSave("Save File", fileName, "*.dpv");
  if (fileName == "") exit(0);

  defaultFileLocation = filedir(fileName); //Get just the directory structure

  output(fileName) {
    addHeader();            //Static header
    addFeeders(layer);      //Calculate the needed feeders
    addBatch();             //Array of PCBs?
    addComponents(layer);   //You know, the things we're trying to place?
    addICTray();            //Add any IC tray info here.
    addPCBCalibrate();      //Add flag?
    addFiducials();         //Add the fiducial/mark information
    addCalibrationFactor(); //Add the calibration factor
  }  
}

/**
 * Adds the opening header information to the dpv file
 */
void addHeader()
{
  //File header
  printf("separated\n");
  printf("FILE,SparkFun_Conversion_Script.dpv\n");
  printf("PCBFILE,SparkFun_Conversion_Script\n");
  printf("DATE,2017/11/27\n"); //Todo pull in current date/time
  printf("TIME,14:42:01\n");
  printf("PANELYPE,0\n"); //Typo is correct. Type 0 = batch of PCBs. Type 1 = panel of PCBs. See addBatch() for info.
  printf("\n");
}

/**
 * Figures out the feeders needed and creates a material stack
 * @param   position    Top (0) or bottom (1) layer placement
 */
void addFeeders(int position)
{
  //Create Material Stack
  printf("\n");
  printf("Table,No.,ID,DeltX,DeltY,FeedRates,Note,Height,Speed,Status,SizeX,SizeY\n");

  int stackNumber = 0;

  //Stop at MAX_FEEDER-1 because feeder 30 is the "No Mount" feeder from the spreadsheet
  for(int i = 1; i <= MAX_FEEDER - 1; i++){
    //Check if feeder is used
    int used = 0;
    for(int k = 0; k < pnpCount; k++){
      if(pnpPos[k] == position && pnpFeeder[k] == i){
        used = 1;
		break;
      }
    }

    if(used){
      //Table,No.,ID,DeltX,DeltY,
      //FeedRates,Note,Height,Speed,
      //Status,SizeX,SizeY

      //0b.0000.0ABC
      //A = 1 = Use Vision
      //A = 0 = No Vision
      //B = 1 = Use Vacuum Detection
      //B = 0 = No Vacuum Detection
      //C = 1 = Skip placement
      //C = 0 = Place this component
      //Example: 3 = no place, vac, no vis

      int mountValue = 0;
      if(stringTrim(getFeederParameter(i, COL_PLACE)) == "N"){
        mountValue += 1;  //Skip
      }
      if(stringTrim(getFeederParameter(i, COL_CHECK_VAC)) == "Y"){
        mountValue += 2;  //Skip
      }
      if(stringTrim(getFeederParameter(i, COL_USE_VISION)) == "Y"){
        mountValue += 4;  //Skip
      }

      //Station,0,1,0,0,4, 0.1uF,0.5,0,6,0,0
      printf("Station, %d, %d, %s, %s, %s, %s, %s, %s, %d, %2.0f, %2.0f\n",
             stackNumber, i, 
             getFeederParameter(i, COL_XOFFSET), getFeederParameter(i, COL_YOFFSET),
             getFeederParameter(i, COL_SPACING), getFeederParameter(i, COL_COMPNAME), 
             getFeederParameter(i, COL_HEIGHT), getFeederParameter(i, COL_SPEED), mountValue, 
             strtod(getFeederParameter(i, COL_WIDTH))*100, 
             strtod(getFeederParameter(i, COL_LENGTH))*100
      ); 

      stackNumber++;
    }
  }
}

/**
 * Add panel definition
 * NOTE: Currently not implemented
 */
void addBatch()
{
  //Batch is where the user takes multiple copies of the same design and mounts them
  //into the machine at the same time.
  //Doing an array is where you have one PCB but X number of copies panelized into an array

  //If you are doing a batch then the header is
  //PANELYPE,0
  //If you are doing an array then the header is
  //PANELYPE,1
  //Typo is correct.

  printf("\n");

  //When there is a batch of boards it looks like this
  printf("Table,No.,ID,DeltX,DeltY\n");
  printf("Panel_Coord,0,1,0,0\n");

  //When you define an array you get this:
  //Table,No.,ID,IntervalX,IntervalY,NumX,NumY
  // IntervalX = x spa8cing. Not sure if this is distance between array
  // NumX = number of copies in X direction
  //Panel_Array,0,1,0,0,2,2

  //If you have an X'd out PCB in the array you can add a skip record.
  //When you add a skip, you get another
  //Panel_Array,1,4,0,0,2,2 //Skip board #4 in the array
  //This doesn't quite make sense but skips will most likely NOT be automated (user will input an X'd out board during job run)

}

/**
 * Add all the components to the output file
 * @param   position      Top (0) or bottom (1) layer placement
 */
void addComponents(int position)
{
  printf("\n");
  printf("Table,No.,ID,PHead,STNo.,DeltX,DeltY,Angle,Height,Skip,Speed,Explain,Note\n");

  int componentNumber = 0;
  int componentID = 1;

  for(int i = 0; i < pnpCount; i++){
    if(pnpPos[i] == position && pnpFeeder[i] > 0 && pnpFeeder[i] != FEEDER_NO_MOUNT){
      //Most all Eagle FPs are correct but we have to subtract 90 because
      //the tapes are mounted 90 degrees from the board
      real convertedAngle = pnpAngle[i] - 90;
      //However, some feeders/FPs were designed not horizontal so we correct on a component by component basis
	  real componentRotation = strtod(getFeederParameter(pnpFeeder[i], COL_RELTAPE));
	  convertedAngle = convertedAngle + componentRotation;
	  
      if (convertedAngle > 180) convertedAngle -= 360; //CharmHigh machine expects rotation of -180 to 180
      if (convertedAngle < -180) convertedAngle += 360; //CharmHigh machine expects rotation of -180 to 180

      int speed = strtol(getFeederParameter(pnpFeeder[i], COL_SPEED));
      if(speed == 100){speed = 0;}  //100% is value 0

      //0b.0000.0ABC
      //A = 1 = Use Vision
      //A = 0 = No Vision
      //B = 1 = Use Vacuum Detection
      //B = 0 = No Vacuum Detection
      //C = 1 = Skip placement
      //C = 0 = Place this component
      //Example: 3 = no place, vac, no vis

      int mountValue = 0;
      if(stringTrim(getFeederParameter(pnpFeeder[i], COL_PLACE)) == "N"){
        mountValue += 1;  //Skip
      }
      if(stringTrim(getFeederParameter(pnpFeeder[i], COL_CHECK_VAC)) == "Y"){
        mountValue += 2;  //Skip
      }
      if(stringTrim(getFeederParameter(pnpFeeder[i], COL_USE_VISION)) == "Y"){
        mountValue += 4;  //Skip
      }

      printf("EComponent, %d, %d, %s, %d, %.2f, %.2f, %.2f, %.2f, %d, %d, %s, %s\n",
             componentNumber, componentID, getFeederParameter(pnpFeeder[i], COL_HEAD), pnpFeeder[i],
             u2mm(transformCoordinateX(pnpX[i], pnpPos[i])), 
             u2mm(transformCoordinateY(pnpY[i], pnpPos[i])), 
             convertedAngle, strtod(getFeederParameter(pnpFeeder[i], COL_HEIGHT)),
             mountValue, speed, 
             pnpDesignator[i], getFeederParameter(pnpFeeder[i], COL_COMPNAME)); //mountValue: 6 is to place, 7 is to skip

      //Example output
      //Table,No.,ID,PHead,STNo.,DeltX,DeltY,Angle,Height,Skip,Speed,Explain,Note
      //EComponent,0,1,1,1,16.51,12.68,0,0.5,6,0,C4, 0.1uF

      componentNumber++;
      componentID++;
    }
  }
}

/**
 * Add any IC tray info
 * NOTE: Currently not implemented
 */
void addICTray()
{
  printf("\n");
  printf("Table,No.,ID,CenterX,CenterY,IntervalX,IntervalY,NumX,NumY,Start\n");
}

/**
 * Add pcb calibration info
 * NOTE: Currently not implemented
 */
void addPCBCalibrate()
{
  //Flags to say what type and if calibration of the board has been done
  printf("\n");
  printf("Table,No.,nType,nAlg,nFinished\n");
  printf("PcbCalib,0,0,0,0\n");

  //nType: 0 = use components as calibration marks, 1 = use marks as calibration marks
  //nFinished: ? 0 = you haven't cal'd a board, 1 = you have cal'd the board
}

/**
 * Add fiducial info
 * NOTE: Currently not implemented
 */
void addFiducials()
{
  //Adds the fiducials or mark information about this board or panel
  //TODO - Should we pull in the marks from the PCB file? It might make better
  //sense to have user do this manually as it will be pretty specific.
  printf("\n");
  printf("Table,No.,ID,offsetX,offsetY,Note\n");
  printf("CalibPoint,0,1,3.14,12.66,Mark1\n");
  printf("CalibPoint,1,2,22.16,12.66,Mark2\n");
}

/**
 * Add calibration factor
 */
void addCalibrationFactor()
{
  //Add the calibration factor. This is all the offsets calculated when the
  //PCB is calibrated. We don't have to set anything here because the program
  //will calculate things after user calibrates the PCB.

  printf("\n");
  printf("Table,No.,DeltX,DeltY,AlphaX,AlphaY,BetaX,BetaY,DeltaAngle\n");
  printf("CalibFator,0,0,0,0,0,1,1,0\n"); //Typo is required
}





/** 
 * Download the feeder data from the server
 * or load it from CSV
 */ 
void downloadFeederData(){
  if(feederListMode ==  0) { //Local CSV
    numberOfFeeders = fileread(availableFeederList, filedir(argv[0]) + feederCSV);
  } else {                  //Download data from url / google spreadsheets
    numberOfFeeders = netget(availableFeederList, feederListUrl);
  }

  // Check if everything was ok
  if (numberOfFeeders == 0){
    dlgMessageBox("Error: Feeder file not found.", "OK");
    exit(0);
  }

  //Process feeder data to be TSV instead of CSV and split headline and data
  availableFeederHeadline = stringReplace(availableFeederList[0], ",", "\t");
  for(int i = 1; i < numberOfFeeders; i++){
    availableFeederList[i-1] = stringReplace(availableFeederList[i], ",", " \t");
  }
  availableFeederList[numberOfFeeders-1] = "";
  numberOfFeeders--;

  //If enabled, autodetect the row columns
  if(autodetectColumns){
    parseRowsByHeader();
  }
}
