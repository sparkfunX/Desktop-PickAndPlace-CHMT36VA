#usage "<b>Generates Pick and Place data for Charmhigh machines</b>\n"
"<p>"
"Generates a .dpv work file for CharmHigh Pick and Place Machines"
"<author>Author: Nathan Seidle, nathan@sparkfun.com</author>"
"<author>Author: Bernhard Woerndl-Aichriedler, bwa@xdevelop.at</author>"

// THIS PROGRAM IS PROVIDED AS IS AND WITHOUT WARRANTY OF ANY KIND, EXPRESSED OR IMPLIED
 
#include "Include_String.ulp"
#include "Include_Tables.ulp"

//Config options we want to save
real      offsetY             = 0.0; 
real      offsetX             = 0.0;
int       enableTop           = 1;
int       enableBottom        = 1;
int       feederListMode      = 1;
string    feederListUrl       = "https://docs.google.com/spreadsheets/d/1t7BfV9FiJE20SNKypvWN8WfetIBiayv5uGflU4kCefE/export?format=csv&id=1t7BfV9FiJE20SNKypvWN8WfetIBiayv5uGflU4kCefE&gid=0";
string    feederCSV           = "feeders.csv";
int       trayListMode        = 1;
string    trayListUrl         = "https://docs.google.com/spreadsheets/d/1t7BfV9FiJE20SNKypvWN8WfetIBiayv5uGflU4kCefE/export?format=csv&id=1t7BfV9FiJE20SNKypvWN8WfetIBiayv5uGflU4kCefE&gid=370861540";
string    trayCSV             = "trays.csv";
int       autodetectColumns   = 1;
int       flipHorizontal      = 1;
string 	  defaultFileLocation = "";
int       useAutomaticOffset  = 1;
int       useFiducials        = 1;
int       numBoardsInPanelX   = 1;
int       numBoardsInPanelY   = 1;
real      panelOffsetX        = 0.0;
real      panelOffsetY        = 0.0;
int       panelMode           = 0;
int       panelise            = 0;

string pnpName[];
string pnpDesignator[];
int    pnpX[];
int    pnpY[];
real   pnpAngle[];
int    pnpFeeder[];
int    pnpPos[];    //Top or bottom
int    pnpCount;    
int    pnpStatsPartsTotal;
int    pnpStatsPartsOk;
int    pnpStatsPartsNew;
int    pnpStatsPartsDnp;
int    pnpStatsPartsError;
string pnpBasefile;

int maxX        = 0;
int minX        = 0;
int maxY        = 0;
int minY        = 0;
int initialized = 0;
real originX    = 0;
real originY    = 0;
real widthX     = 0;
real widthY     = 0;

int MAX_FEEDER    		= 99;
int FEEDER_FIDUCIAL   = 1000;
int FEEDER_NEW    		= -1;
int FEEDER_DNP    		= 0; //This comes from eagle brd file
int FEEDER_NO_MOUNT    	= 999; //This comes from spreadsheet

string configFile  = filesetext(argv[0], ".cfg");

int usedFiducial[];

/**
 * Write the ULP configuration to the config file
 */
void configWrite(){
  output(configFile){
    printf("%.5f\n", offsetX);
    printf("%.5f\n", offsetY);
    printf("%d\n",   enableTop);
    printf("%d\n",   enableBottom);
    printf("%d\n",   feederListMode);
    printf("%s\n",   feederListUrl);
    printf("%s\n",   feederCSV);
    printf("%d\n",   autodetectColumns);
    printf("%d\n",   flipHorizontal);
    printf("%s\n",   defaultFileLocation);
    printf("%d\n",   useAutomaticOffset);
    printf("%d\n",   trayListMode);
    printf("%s\n",   trayListUrl);
    printf("%s\n",   trayCSV);
    printf("%d\n",   useFiducials);
    printf("%d\n",   numBoardsInPanelX);
    printf("%d\n",   numBoardsInPanelY);
    printf("%.5f\n",   panelOffsetX);
    printf("%.5f\n",   panelOffsetY);
    printf("%d\n",   panelise);
    printf("%d\n",   panelMode);

  }
}

/**
 * Read the ULP configuration from the config file
 */
void configRead() {
  if(filesize(configFile)){ //Check if file exists
    string data[];
    int line = fileread(data, configFile);
    if(line >= 5){
      offsetX            	= strtod(data[0]);
      offsetY            	= strtod(data[1]);
      enableTop          	= strtol(data[2]);
      enableBottom       	= strtol(data[3]);
      feederListMode     	= strtol(data[4]);
      feederListUrl      	= data[5];
      feederCSV          	= data[6];
      autodetectColumns  	= strtol(data[7]);
      flipHorizontal     	= strtol(data[8]);
      defaultFileLocation	= data[9];
      useAutomaticOffset	= strtol(data[10]);
      trayListMode        = strtol(data[11]);
      trayListUrl         = data[12];
      trayCSV             = data[13];
      useFiducials        = strtol(data[14]);
      numBoardsInPanelX   = strtol(data[15]);
      numBoardsInPanelY   = strtol(data[16]);
      panelOffsetX        = strtol(data[17]);
      panelOffsetY        = strtol(data[18]);
      panelise            = strtol(data[19]);
      panelMode           = strtol(data[20]);
    }
  }
}

/**
 * Get the X-width of the board in Eagle-Uits
 * This function is automatic offset aware
 */
int getWidthX(){
  int w = maxX-minX;
  if(!useAutomaticOffset){
    w = mm2u(widthX);
  }
  return w;
}

/**
 * Get the Y-width of the board in Eagle-Uits
 * This function is automatic offset aware
 */
int getWidthY(){
  int w = maxY-minY;
  if(!useAutomaticOffset){
    w = mm2u(widthY);
  }
  return w;
}

/**
 * Get the X-width of the board in Eagle-Uits
 * This function is automatic offset aware
 */
int getMaxX(){
  int w = maxX;
  if(!useAutomaticOffset){
    w = mm2u(widthX);
  }
  return w;
}

/**
 * Get the Y-width of the board in Eagle-Uits
 * This function is automatic offset aware
 */
int getMaxY(){
  int w = maxY;
  if(!useAutomaticOffset){
    w = mm2u(widthY);
  }
  return w;
}

/**
 * Get the X-origin of the board in Eagle-Uits
 * This function is automatic offset aware
 */
int getOriginX(){
  int o = minX;
  if(!useAutomaticOffset){
    o = mm2u(originX);
  }
  return o;
}
/**
 * Get the Y-origin of the board in Eagle-Uits
 * This function is automatic offset aware
 */
int getOriginY(){
  int o = minY;
  if(!useAutomaticOffset){
    o = mm2u(originY);
  }
  return o;
}


/**
 * This function transforms the X coordinates
 * according to the settings
 * @return Transformed X coordinate
 */
int transformCoordinateX(int x, int pos){
  int oX = getOriginX();
  int wX = getMaxX();

  //Handle Top + Bottom H/V Flip transformation
  int offset = 0;
  if(pos == 0){
    offset = x - oX;
  } else {
    if(flipHorizontal){
      offset = wX - x;
    } else {      
      offset = x - oX;
    }
  }
  return offset + mm2u(offsetX);
}

/**
 * This function transforms the Y coordinates
 * according to the settings
 * @return Transformed X coordinate
 */
int transformCoordinateY(int y, int pos){
  int oY = getOriginY();
  int wY = getMaxY();

  //Handle Top + Bottom H/V Flip transformation
  int offset = 0;
  if(pos == 0){
    offset = y - oY;
  } else {
    if(flipHorizontal){
      offset = y - oY;
    } else {      
      offset = wY - y;
    }    
  }
  return offset + mm2u(offsetY);
}


/**
 * Adds the opening header information to the dpv file
 */
void addHeader() {
  //File header
  printf("separated\n");
  printf("FILE,SparkFun_Conversion_Script.dpv\n");
  printf("PCBFILE,SparkFun_Conversion_Script\n");
  printf("DATE,2017/11/27\n"); //Todo pull in current date/time
  printf("TIME,14:42:01\n");
  printf("PANELYPE,1\n"); //Typo is correct. Type 0 = batch of PCBs. Type 1 = panel of PCBs. See addBatch() for info.
  printf("\n");
}

/**
 * Figures out the feeders needed and creates a material stack
 * @param   position    Top (0) or bottom (1) layer placement
 */
void addFeeders(int position) {
  //Create Material Stack
  printf("\n");
  printf("Table,No.,ID,DeltX,DeltY,FeedRates,Note,Height,Speed,Status,SizeX,SizeY\n");

  int stackNumber = 0;

  for(int i = 1; i <= MAX_FEEDER; i++){
    //Ignore DNP, NoMount and fiducials
    if(i == FEEDER_NO_MOUNT || i == FEEDER_DNP || i == FEEDER_FIDUCIAL){
      continue;
    }


    //Check if feeder is used
    int used = 0;
    for(int k = 0; k < pnpCount; k++){
      if(pnpPos[k] == position && pnpFeeder[k] == i){
        used = 1;
		break;
      }
    }

    if(used){
      //Table,No.,ID,DeltX,DeltY,
      //FeedRates,Note,Height,Speed,
      //Status,SizeX,SizeY

      //0b.0000.0ABC
      //A = 1 = Use Vision
      //A = 0 = No Vision
      //B = 1 = Use Vacuum Detection
      //B = 0 = No Vacuum Detection
      //C = 1 = Skip placement
      //C = 0 = Place this component
      //Example: 3 = no place, vac, no vis

      int mountValue = 0;
      if(stringTrim(getFeederParameter(i, COL_PLACE)) == "N"){
        mountValue += 1;  //Skip
      }
      if(stringTrim(getFeederParameter(i, COL_CHECK_VAC)) == "Y"){
        mountValue += 2;  //Skip
      }
      if(stringTrim(getFeederParameter(i, COL_USE_VISION)) == "Y"){
        mountValue += 4;  //Skip
      }

      //Station,0,1,0,0,4, 0.1uF,0.5,0,6,0,0
      printf("Station, %d, %d, %s, %s, %s, %s, %s, %s, %d, %2.0f, %2.0f\n",
             stackNumber, i, 
             getFeederParameter(i, COL_XOFFSET), getFeederParameter(i, COL_YOFFSET),
             getFeederParameter(i, COL_SPACING), getFeederParameter(i, COL_COMPNAME), 
             getFeederParameter(i, COL_HEIGHT), getFeederParameter(i, COL_SPEED), mountValue, 
             strtod(getFeederParameter(i, COL_WIDTH))*100, 
             strtod(getFeederParameter(i, COL_LENGTH))*100
      ); 

      stackNumber++;
    }
  }
}

/**
 * Add panel definition
 * NOTE: Currently not implemented
 */
void addBatch() {
  //Batch is where the user takes multiple copies of the same design and mounts them
  //into the machine at the same time.
  //Doing an array is where you have one PCB but X number of copies panelised into an array

  //If you are doing a batch then the header is
  //PANELYPE,0
  //If you are doing an array then the header is
  //PANELYPE,1
  //Typo is correct.

  printf("\n");

  //When there is a batch of boards it looks like this
  printf("Table,No.,ID,IntervalX,IntervalY,NumX,NumY\n");
  //printf("Panel_Coord,0,1,0,0\n");
  if(panelise){
    real offsetX = panelOffsetX;
    real offsetY = panelOffsetY;
    if(panelMode == 0){
      offsetX += u2mm(getWidthX());
      offsetY += u2mm(getWidthY());
    }

    printf("Panel_Array,0,1,%.5f,%.5f,%d,%d\n", offsetX, offsetY, numBoardsInPanelX, numBoardsInPanelY);
  }
  else {
    printf("Panel_Array,0,1,0,0,1,1\n");
  }
  

  //When you define an array you get this:
  //Table,No.,ID,IntervalX,IntervalY,NumX,NumY
  // IntervalX = x spa8cing. Not sure if this is distance between array
  // NumX = number of copies in X direction
  //Panel_Array,0,1,0,0,2,2

  //If you have an X'd out PCB in the array you can add a skip record.
  //When you add a skip, you get another
  //Panel_Array,1,4,0,0,2,2 //Skip board #4 in the array
  //This doesn't quite make sense but skips will most likely NOT be automated (user will input an X'd out board during job run)
}

/**
 * Add all the components to the output file
 * @param   position      Top (0) or bottom (1) layer placement
 */
void addComponents(int position){
  printf("\n");
  printf("Table,No.,ID,PHead,STNo.,DeltX,DeltY,Angle,Height,Skip,Speed,Explain,Note\n");

  int componentNumber = 0;
  int componentID = 1;

  for(int i = 0; i < pnpCount; i++){
    if(pnpPos[i] == position && pnpFeeder[i] > 0 && pnpFeeder[i] != FEEDER_NO_MOUNT && pnpFeeder[i] != FEEDER_FIDUCIAL){
      //Most all Eagle FPs are correct but we have to subtract 90 because
      //the tapes are mounted 90 degrees from the board
      real convertedAngle = pnpAngle[i] - 90;

      //For trays, we don't need to correct anything,
      //just place them in the tray as in the eagle footprint
      if(pnpFeeder[i] >= 88){
        convertedAngle = pnpAngle[i];
      }

      //However, some feeders/FPs were designed not horizontal so we correct on a component by component basis
	    real componentRotation = strtod(getFeederParameter(pnpFeeder[i], COL_RELTAPE));
	    convertedAngle = convertedAngle + componentRotation;
	  
      if (convertedAngle > 180) convertedAngle -= 360; //CharmHigh machine expects rotation of -180 to 180
      if (convertedAngle < -180) convertedAngle += 360; //CharmHigh machine expects rotation of -180 to 180

      int speed = strtol(getFeederParameter(pnpFeeder[i], COL_SPEED));
      if(speed == 100){speed = 0;}  //100% is value 0

      //0b.0000.0ABC
      //A = 1 = Use Vision
      //A = 0 = No Vision
      //B = 1 = Use Vacuum Detection
      //B = 0 = No Vacuum Detection
      //C = 1 = Skip placement
      //C = 0 = Place this component
      //Example: 3 = no place, vac, no vis

      int mountValue = 0;
      if(stringTrim(getFeederParameter(pnpFeeder[i], COL_PLACE)) == "N"){
        mountValue += 1;  //Skip
      }
      if(stringTrim(getFeederParameter(pnpFeeder[i], COL_CHECK_VAC)) == "Y"){
        mountValue += 2;  //Skip
      }
      if(stringTrim(getFeederParameter(pnpFeeder[i], COL_USE_VISION)) == "Y"){
        mountValue += 4;  //Skip
      }

      printf("EComponent, %d, %d, %s, %d, %.2f, %.2f, %.2f, %.2f, %d, %d, %s, %s\n",
             componentNumber, componentID, getFeederParameter(pnpFeeder[i], COL_HEAD), pnpFeeder[i],
             u2mm(transformCoordinateX(pnpX[i], pnpPos[i])), 
             u2mm(transformCoordinateY(pnpY[i], pnpPos[i])), 
             convertedAngle, strtod(getFeederParameter(pnpFeeder[i], COL_HEIGHT)),
             mountValue, speed, 
             pnpDesignator[i], getFeederParameter(pnpFeeder[i], COL_COMPNAME)); //mountValue: 6 is to place, 7 is to skip

      //Example output
      //Table,No.,ID,PHead,STNo.,DeltX,DeltY,Angle,Height,Skip,Speed,Explain,Note
      //EComponent,0,1,1,1,16.51,12.68,0,0.5,6,0,C4, 0.1uF

      componentNumber++;
      componentID++;
    }
  }
}

/**
 * Add any IC tray info
 * NOTE: Currently not implemented
 */
void addICTray() {
  //Material Stacks from 88 to 99 are for IC trays
  //ICTray,0,88,209,55.5,353,55.5,7,1,0
  printf("\n");
  printf("Table,No.,ID,CenterX,CenterY,IntervalX,IntervalY,NumX,NumY,Start\n");
  for(int i = 0; i < numberOfTrays; i++){
    string id = getTrayParameterByLine(i, COL2_TRAYID);
    int trayid = strtol(id);

    if(stringTrim(id) != ""){
      //Our IC has a size to it, so we need to add that to our positions
      real x1 = strtod(getTrayParameterByLine(i, COL2_X1));
      real y1 = strtod(getTrayParameterByLine(i, COL2_Y1));
      real x2 = strtod(getTrayParameterByLine(i, COL2_X2));
      real y2 = strtod(getTrayParameterByLine(i, COL2_Y2));

      real sizex = strtod(getFeederParameter(trayid, COL_LENGTH));
      real sizey = strtod(getFeederParameter(trayid, COL_WIDTH));

      //x acis is normal
      x1 = x1 + sizex/2;
      x2 = x2 + sizex/2;

      //y axis is inverted
      y1 = y1 - sizey/2;
      y2 = y2 - sizey/2;

      printf("ICTray,%d,%d, %.2f, %.2f, %.2f, %.2f, %s, %s, 0\n", 
        i, trayid, x1, y1, x2, y2, getTrayParameterByLine(i, COL2_XCOUNT), getTrayParameterByLine(i, COL2_YCOUNT)
     );
    }
  } 
}

/**
 * Add fiducial info
 */
void addFiducials(int position) {
  if(useFiducials){
    //PCB calibration is done with marks instead of parts
    printf("\n");
    printf("Table,No.,nType,nAlg,nFinished\n");
    printf("PcbCalib,0,1,0,0\n");

    printf("\n");
    printf("Table,No.,ID,offsetX,offsetY,Note\n");

    int componentNumber = 0; 
    int componentID = 1; 
    for(int i = 0; i < pnpCount; i++){
      if(pnpPos[i] == position && pnpFeeder[i] == FEEDER_FIDUCIAL && usedFiducial[i]){


        printf("CalibPoint,%d,%d,%.2f,%.2f,%s\n",
               componentNumber, componentID,
               u2mm(transformCoordinateX(pnpX[i], pnpPos[i])), 
               u2mm(transformCoordinateY(pnpY[i], pnpPos[i])), 
               pnpDesignator[i]); //mountValue: 6 is to place, 7 is to skip

        //Example output
        //Table,No.,ID,PHead,STNo.,DeltX,DeltY,Angle,Height,Skip,Speed,Explain,Note
        //EComponent,0,1,1,1,16.51,12.68,0,0.5,6,0,C4, 0.1uF

        componentNumber++;
        componentID++;
      }
    }   
  } else {
    printf("\n");
    printf("Table,No.,nType,nAlg,nFinished\n");
    //PCB calibration is done using parts
    printf("PcbCalib,0,0,0,0\n"); 
    //nType: 0 = use components as calibration marks, 1 = use marks as calibration marks
    //nFinished: ? 0 = you haven't cal'd a board, 1 = you have cal'd the board
    printf("\n");
    printf("Table,No.,ID,offsetX,offsetY,Note\n"); 
    //Some random marks, that will be ignored
    printf("CalibPoint,0,1,3.14,12.66,Mark1\n");
    printf("CalibPoint,1,2,22.16,12.66,Mark2\n");  
  }
}

/**
 * Add calibration factor
 */
void addCalibrationFactor() {
  //Add the calibration factor. This is all the offsets calculated when the
  //PCB is calibrated. We don't have to set anything here because the program
  //will calculate things after user calibrates the PCB.

  printf("\n");
  printf("Table,No.,DeltX,DeltY,AlphaX,AlphaY,BetaX,BetaY,DeltaAngle\n");
  printf("CalibFator,0,0,0,0,0,1,1,0\n"); //Typo is required
}

/** 
 * Process all information and create the output file
 */
void writeOutputFile(int layer, string prefix) {
  string fileName = filesetext(pnpBasefile, prefix + ".dpv");

  if(defaultFileLocation != "")
  {
    fileName = defaultFileLocation + filesetext(filename(pnpBasefile), prefix + ".dpv");
  }

  //Prompt user for location to store file
  fileName = dlgFileSave("Save File", fileName, "*.dpv");
  if (fileName == "") exit(0);

  defaultFileLocation = filedir(fileName); //Get just the directory structure

  output(fileName) {
    addHeader();            //Static header
    addFeeders(layer);      //Calculate the needed feeders
    addBatch();             //Array of PCBs?
    addComponents(layer);   //You know, the things we're trying to place?
    addICTray();            //Add any IC tray info here.
    addFiducials(layer);    //Add the fiducial/mark information
    addCalibrationFactor(); //Add the calibration factor
  }  
}

string convertUrl(string url) {
  int ind=strstr(url,"edit");

  if(ind != -1){
    int n = strstr(url,"/d/")+3;
    int l = strstr(url,"#gid=")+1;

    string basUrl = strsub(url,0,ind);
    string id = strsub(url,n,(ind-n-1));
    string gid = strsub(url,l);

    url = basUrl + "export?format=csv&id=" + id + "&" + gid;
  }
  return url;
}

/** 
 * Download the feeder data from the server
 * or load it from CSV
 */ 
void downloadFeederData(){
  if(feederListMode ==  0) { //Local CSV
    numberOfFeeders = fileread(availableFeederList, filedir(argv[0]) + feederCSV);
  } else {                  //Download data from url / google spreadsheets
    string url = convertUrl(feederListUrl);
    numberOfFeeders = netget(availableFeederList, url);
  }

  // Check if everything was ok
  if (numberOfFeeders <= 0){
    dlgMessageBox("Error: Feeder file not found.", "OK");
    exit(0);
  }

  //Process feeder data to be TSV instead of CSV and split headline and data
  availableFeederHeadline = stringReplace(availableFeederList[0], ",", "\t");
  for(int i = 1; i < numberOfFeeders; i++){
    if(strstr(availableFeederList[i],"Stop")!=-1) {
      numberOfFeeders=i;
      availableFeederList[numberOfFeeders] = "";
      break;
    }

    availableFeederList[i-1] = stringReplace(availableFeederList[i], ",", " \t");
  }
  availableFeederList[numberOfFeeders-1] = "";
  numberOfFeeders--;

  //If enabled, autodetect the row columns
  if(autodetectColumns){
    parseFeederColsByHeader();
  }
  initFeederIndex();
}

/** 
 * Download the tray data from the server
 * or load it from CSV
 */ 
void downloadTrayData(){
  if(trayListMode ==  0) { //Local CSV
    numberOfTrays = fileread(availableTrayList, filedir(argv[0]) + trayCSV);
  } else {                  //Download data from url / google spreadsheets
    string url = convertUrl(trayListUrl);
    numberOfTrays = netget(availableTrayList, url);
  }

  // Check if everything was ok
  if (numberOfTrays <= 0){
    dlgMessageBox("Error: Feeder file not found.", "OK");
    exit(0);
  }

  //Process feeder data to be TSV instead of CSV and split headline and data
  availableTrayHeadline = stringReplace(availableTrayList[0], ",", "\t");
  for(int i = 1; i < numberOfTrays; i++){
    if(strstr(availableTrayList[i],"Stop")!=-1) {
      numberOfTrays=i;
      availableTrayList[numberOfTrays] = "";
      break;
    }

    availableTrayList[i-1] = stringReplace(availableTrayList[i], ",", " \t");
  }
  availableTrayList[numberOfTrays-1] = "";
  numberOfTrays--;

  //If enabled, autodetect the row columns
  if(autodetectColumns){
    parseTrayColsByHeader();
  }
}

/**
 * Process the coordinates to determine min/max of the outline
 * param  x   X coordinate of the current element
 * param  Y   Y coordinate of the current element
 */
void setCoordinates(int x, int y) {
  if(!initialized) {
    maxX = x;
    minX = x;
    maxY = y;
    minY = y;
    initialized = 1;
  }

  if(x < minX) {
    minX = x;
  }
  if(y < minY) {
    minY = y;
  }
  if(y > maxY) {
    maxY = y;  
  }
  if(x > maxX) {
    maxX = x;  
  }
}

/**
 * Load all required information from the board
 */
void loadBoardInformation() {
  pnpCount            = 0;
  pnpStatsPartsTotal  = 0;
  pnpStatsPartsOk     = 0;
  pnpStatsPartsNew    = 0;
  pnpStatsPartsDnp    = 0;
  pnpStatsPartsError  = 0;


  //Walk trough all elements for the board
  board(B) {
    pnpBasefile = B.name;

    B.elements(E) {
      int isSmd = 0;
      int isBottom = 0;
      int isTop = 0;

      //Determine centroid offset of the element
      int xmax = -2147483648,
          xmin = 2147483647,
          ymax = xmax,
          ymin = xmin;	  
      E.package.contacts(C) {
        if (C.smd && C.smd.layer == 1) {
          isSmd = 1;
          isTop = 1;

	        //Find centroid of this component
          if (C.x > xmax) xmax = C.x;
          if (C.y > ymax) ymax = C.y;
          if (C.x < xmin) xmin = C.x;
          if (C.y < ymin) ymin = C.y;
        }
        if (C.smd && C.smd.layer == 16) {
          isSmd = 1;
          isBottom = 1;

          if (C.x > xmax) xmax = C.x;
          if (C.y > ymax) ymax = C.y;
          if (C.x < xmin) xmin = C.x;
          if (C.y < ymin) ymin = C.y;
        }
      }

      //If the part is SMD, process it
      if (isSmd) {
		real xCenter = (xmin + xmax) / 2;
   		real yCenter = (ymin + ymax) / 2;
		
        pnpName[pnpCount]       = E.value + '-' + E.package.name;
        pnpDesignator[pnpCount] = E.name;
        pnpX[pnpCount]          = xCenter;
        pnpY[pnpCount]          = yCenter;
        pnpAngle[pnpCount]      = E.angle;
        pnpPos[pnpCount]        = isBottom;

        //If we want to populate the device
        if(E.populate && E.attribute["POPULATE"] != "DNP"){
          pnpFeeder[pnpCount]   = getFeederId(pnpName[pnpCount]);
        } else {
          pnpFeeder[pnpCount]   = FEEDER_DNP;
        }

        //Update stats
        pnpStatsPartsTotal++;
        if(pnpFeeder[pnpCount] == FEEDER_NEW){
          pnpStatsPartsNew++;
        } else if(pnpFeeder[pnpCount] == FEEDER_DNP){
          pnpStatsPartsDnp++;
        } else {
          pnpStatsPartsOk++;
        }

        //searching for the 4 most extreem fiducials on top and bottom
        if(pnpFeeder[pnpCount] == FEEDER_FIDUCIAL){
          if(pnpPos[pnpCount]) {
            if(pnpX[pnpCount]+pnpY[pnpCount]>pnpX[usedFiducial[0]]+pnpY[usedFiducial[0]]){
              usedFiducial[0]=pnpCount;
            }
            if(pnpX[pnpCount]-pnpY[pnpCount]>pnpX[usedFiducial[1]]-pnpY[usedFiducial[1]]){
              usedFiducial[1]=pnpCount;
            }
            if(pnpX[pnpCount]-pnpY[pnpCount]<pnpX[usedFiducial[2]]-pnpY[usedFiducial[2]]){
              usedFiducial[2]=pnpCount;
            }
            if(pnpX[pnpCount]+pnpY[pnpCount]<pnpX[usedFiducial[3]]+pnpY[usedFiducial[3]]){
              usedFiducial[3]=pnpCount;
            }
          }
          else {
            if(pnpX[pnpCount]+pnpY[pnpCount]>pnpX[usedFiducial[4]]+pnpY[usedFiducial[4]]){
              usedFiducial[4]=pnpCount;
            }
            if(pnpX[pnpCount]-pnpY[pnpCount]>pnpX[usedFiducial[5]]-pnpY[usedFiducial[5]]){
              usedFiducial[5]=pnpCount;
            }
            if(pnpX[pnpCount]-pnpY[pnpCount]<pnpX[usedFiducial[6]]-pnpY[usedFiducial[6]]){
              usedFiducial[6]=pnpCount;
            }
            if(pnpX[pnpCount]+pnpY[pnpCount]<pnpX[usedFiducial[7]]+pnpY[usedFiducial[7]]){
              usedFiducial[7]=pnpCount;
            }
          }
        }
        pnpCount++;

        if(isBottom&&isTop){
          real xCenter = (xmin + xmax) / 2;
          real yCenter = (ymin + ymax) / 2;
      
          pnpName[pnpCount]       = E.value + '-' + E.package.name;
          pnpDesignator[pnpCount] = E.name;
          pnpX[pnpCount]          = xCenter;
          pnpY[pnpCount]          = yCenter;
          pnpAngle[pnpCount]      = E.angle;
          pnpPos[pnpCount]        = !isBottom;

          //If we want to populate the device
          if(E.populate && E.attribute["POPULATE"] != "DNP"){
            pnpFeeder[pnpCount]   = getFeederId(pnpName[pnpCount]);
          } else {
            pnpFeeder[pnpCount]   = FEEDER_DNP;
          }

          //Update stats
          pnpStatsPartsTotal++;
          if(pnpFeeder[pnpCount] == FEEDER_NEW){
            pnpStatsPartsNew++;
          } else if(pnpFeeder[pnpCount] == FEEDER_DNP){
            pnpStatsPartsDnp++;
          } else {
            pnpStatsPartsOk++;
          }

          //searching for the 4 most extreem fiducials on top and bottom
          if(pnpFeeder[pnpCount] == FEEDER_FIDUCIAL){
            if(pnpPos[pnpCount]) {
              if(pnpX[pnpCount]+pnpY[pnpCount]>pnpX[usedFiducial[0]]+pnpY[usedFiducial[0]]){
                usedFiducial[0]=pnpCount;
              }
              if(pnpX[pnpCount]-pnpY[pnpCount]>pnpX[usedFiducial[1]]-pnpY[usedFiducial[1]]){
                usedFiducial[1]=pnpCount;
              }
              if(pnpX[pnpCount]-pnpY[pnpCount]<pnpX[usedFiducial[2]]-pnpY[usedFiducial[2]]){
                usedFiducial[2]=pnpCount;
              }
              if(pnpX[pnpCount]+pnpY[pnpCount]<pnpX[usedFiducial[3]]+pnpY[usedFiducial[3]]){
                usedFiducial[3]=pnpCount;
              }
            }
            else {
              if(pnpX[pnpCount]+pnpY[pnpCount]>pnpX[usedFiducial[4]]+pnpY[usedFiducial[4]]){
                usedFiducial[4]=pnpCount;
              }
              if(pnpX[pnpCount]-pnpY[pnpCount]>pnpX[usedFiducial[5]]-pnpY[usedFiducial[5]]){
                usedFiducial[5]=pnpCount;
              }
              if(pnpX[pnpCount]-pnpY[pnpCount]<pnpX[usedFiducial[6]]-pnpY[usedFiducial[6]]){
                usedFiducial[6]=pnpCount;
              }
              if(pnpX[pnpCount]+pnpY[pnpCount]<pnpX[usedFiducial[7]]+pnpY[usedFiducial[7]]){
                usedFiducial[7]=pnpCount;
              }
            }
          }
          pnpCount++;
        }
      }

      //Autodetect to board outline
      B.wires(W) {
        if(W.layer == 20) {
          if(W.arc) {
            setCoordinates(W.arc.x1, W.arc.y1);
            setCoordinates(W.arc.x2, W.arc.y2);
            
            int angle = W.arc.angle2 - W.arc.angle1;
            
            int set_elements = round(angle/90);
            int start_element = round(W.arc.angle1/90);
            start_element = start_element % 4;
            
            for(int i = start_element; i < (start_element + set_elements); i++) {
              if(i == 0) {
                setCoordinates(W.arc.xc - W.arc.radius, W.arc.y1);
              } else if(i == 1) {
                setCoordinates(W.arc.x2, W.arc.yc + W.arc.radius);
              } else if(i == 2) {
                setCoordinates(W.arc.xc + W.arc.radius, W.arc.y1);
              } else if(i == 3) {
                setCoordinates(W.arc.x2, W.arc.yc - W.arc.radius);
              }
            }
          } else {
            setCoordinates(W.x1, W.y1);
            setCoordinates(W.x2, W.y2);
          }
        }
      }

      B.circles(C) {
        if(C.layer == 20) {
          setCoordinates(C.x + C.radius, C.y + C.radius);
          setCoordinates(C.x - C.radius, C.y - C.radius);
        }
      }
    } 
  }


  //convert the values in usedFiducial into somthing realy useful
  int tmp[];
  for (int n=0;n<8;n++) {
    tmp[usedFiducial[n]]=1;
  }
  for (int l=0;l<pnpCount;l++){
    usedFiducial[l] = tmp[l];
  }
}

int tab=0;
string offX = "";
string offY = "";
string pWithX = "";
string pWithY = "";


/** 
 * Update panelise gui
 */
void updatePanelOptions(void) {  
  real offsetX = panelOffsetX;
  real offsetY = panelOffsetY;
  if(panelMode == 0){
    offsetX += u2mm(getWidthX());
    offsetY += u2mm(getWidthY());
  }

  sprintf(offX, "%.2f mm", offsetX);
  sprintf(offY, "%.2f mm", offsetY);

  real width = offsetX*(numBoardsInPanelX-1)  + u2mm(getWidthX());
  real height = offsetY*(numBoardsInPanelY-1) + u2mm(getWidthY());

  sprintf(pWithX, "%.2f mm", width);
  sprintf(pWithY, "%.2f mm", height);
}

/**
 * GUI Data
 */
void showPanelOptions(void) {
  dlgDialog("Panel options") {

    updatePanelOptions();

    dlgVBoxLayout {
      dlgHBoxLayout {
        dlgLabel("<img src=\"helpGrafic.png\">");
        dlgVBoxLayout {
          dlgGroup("") {
            dlgHBoxLayout {
              dlgLabel("Repeat X:");
              dlgIntEdit(numBoardsInPanelX,1,999999);
            }
            dlgHBoxLayout {
              dlgLabel("Repeat Y:");
              dlgIntEdit(numBoardsInPanelY,1,999999);
            }
            dlgSpacing(15);
            dlgHBoxLayout {
              dlgRadioButton("spacing between designs",panelMode);
              dlgRadioButton("spacing between origins",panelMode);
            }
            dlgHBoxLayout {
              dlgLabel("Spacing X:");
              dlgRealEdit(panelOffsetX,-999999,999999);
              dlgLabel("mm");
            }
            dlgHBoxLayout {
              dlgLabel("Spacing Y:");
              dlgRealEdit(panelOffsetY,-999999,999999);
              dlgLabel("mm");
            }
            dlgSpacing(15);
            dlgHBoxLayout {
              dlgLabel("Origin spacing X:");
              dlgStretch(1);
              dlgLabel(offX,1);
            }
            dlgHBoxLayout {
              dlgLabel("Origin spacing Y:");
              dlgStretch(1);
              dlgLabel(offY,1);
            }
            dlgHBoxLayout {
              dlgLabel("Panel width:");
              dlgStretch(1);
              dlgLabel(pWithX,1);
            }
            dlgHBoxLayout {
              dlgLabel("Panel height:");
              dlgStretch(1);
              dlgLabel(pWithY,1);
            }
            dlgPushButton("Update") {
              updatePanelOptions();
            }
          }
          dlgStretch(1);
          dlgHBoxLayout{
            dlgStretch(1);
            dlgPushButton("OK") {
              dlgAccept();
            }
          }
        }
      }
    }
  };
}

int showListOfDevices() {
  int selected = 0;
  int sorted = 0;
  int sortedFeedersUsed = 1;
  int quantity = 1;
  configRead();
  downloadFeederData();
  downloadTrayData();

  loadBoardInformation();
  widthX = u2mm(maxX);
  widthY = u2mm(maxY);

  //Re-display dialog as long as we don't abort
  while(1) {

    //Generate / refresh the part list
    string partlist[];
    pnpStatsPartsError = 0;
    for(int i = 0; i < pnpCount; i++){
      partlist[i] = "";
      string feeder = "";

  	  //Check the feeder spreadsheet to see if we should ignore this part (may be a fiducial)
      string noMountAlias = getFeederParameterByLine(29, COL_ALIAS);

      if(pnpFeeder[i] == FEEDER_NEW){
        feeder = "No feeder assigned!";
      } else if(pnpFeeder[i] == FEEDER_FIDUCIAL){
        feeder = "Fiducial";
        if(usedFiducial[i]){
          feeder += " used";
        }
      } else if(pnpFeeder[i] == FEEDER_DNP){
        feeder = "No Mount";
      } else if(pnpFeeder[i] == FEEDER_NO_MOUNT){
        feeder = "No Mount";
      } else {
        sprintf(feeder, "%d", pnpFeeder[i]);
      }

      int tX = transformCoordinateX(pnpX[i], pnpPos[i]);
      int tY = transformCoordinateY(pnpY[i], pnpPos[i]);

      if(tX < 0 || tY < 0){
        pnpStatsPartsError++;
      }

      sprintf(partlist[i], "%s\t%s\t%s\t%.2fmm\t%.2fmm\t%.2fmm\t%.2fmm\t%.1f°\t%s", 
          pnpDesignator[i], pnpName[i], (pnpPos[i]==0)?"Top":"Bottom", 
          u2mm(pnpX[i]), u2mm(tX), 
          u2mm(pnpY[i]), u2mm(tY), 
          pnpAngle[i], feeder
      );
    } 
	
  	//Generate Feeders Used list. Helpful for seeing what feeders we need to load or assign
    string listOfUsedFeeders;
  	string usedFeederList[]; //Used in GUI
  	int usedFeederCount = 0;
    for(i = 0; i < pnpCount; i++){

      string feeder = "";
      if(pnpFeeder[i] == FEEDER_NEW){
        feeder = "None";
      } else if(pnpFeeder[i] == FEEDER_DNP){
        feeder = "Do not mount!";
      } else {
        sprintf(feeder, "%d", pnpFeeder[i]);
      }

  	  //Ignore parts from record NoMount row
  	  if(pnpFeeder[i] != FEEDER_NO_MOUNT){
        //If this feeder is new, it doesn't have a nickname  
        if(pnpFeeder[i] == FEEDER_NEW){
          //See if this feeder is already in the list
          if (strstr(listOfUsedFeeders, pnpName[i]) == -1) {
        		//Add this component name to the list of used feeders
        		listOfUsedFeeders += pnpName[i] + '\n';

        		//We don't have a feeder for this component so maintain its name
        		sprintf(usedFeederList[usedFeederCount++], "%s\t%s\t", 
        		  feeder, pnpName[i]
        		);
          }
        }
        //Known feeder: See if this feeder's nickname is already in the list
        else if (strstr(listOfUsedFeeders, getFeederParameter(pnpFeeder[i], COL_COMPNAME) ) == -1){
          //Add this component's nickname to the list of used feeders
          listOfUsedFeeders += getFeederParameter(pnpFeeder[i], COL_COMPNAME) + '\n';
        	
          //We have a nickname for this component from the spreadsheet so use it
          sprintf(usedFeederList[usedFeederCount++], "%s\t%s\t", 
            feeder, getFeederParameter(pnpFeeder[i], COL_COMPNAME)
          );
        }
      }
    } 
		
    //Display main dialog
    int dstatus = dlgDialog("Feeder configuration"){
      dlgHBoxLayout{
        dlgVBoxLayout dlgSpacing(800);
        dlgTabWidget {
          dlgTabPage("Parts Overview") {
            dlgHBoxLayout {
              dlgListView("Designator\tComponent\tPosition\tBoard X\tPlacement X\tBoard Y\tPlacement Y\tAngle\tFeeder", partlist, selected, sorted);
              dlgVBoxLayout {
                dlgGroup("Offset") {
                  dlgRadioButton("Use manual origin and size",     useAutomaticOffset); 
                  dlgHBoxLayout{ dlgLabel("Origin X:\t");                   dlgRealEdit(originX, -10000, 10000); dlgLabel("mm");}  
                  dlgHBoxLayout{ dlgLabel("Origin Y:\t");                   dlgRealEdit(originY, -10000, 10000); dlgLabel("mm");}  
                  dlgHBoxLayout{ dlgLabel("Width:   \t");                   dlgRealEdit(widthX, -10000, 10000);  dlgLabel("mm");}  
                  dlgHBoxLayout{ dlgLabel("Height:  \t");                   dlgRealEdit(widthY, -10000, 10000);  dlgLabel("mm");}  
                  dlgRadioButton("Use automatic offset",  useAutomaticOffset);          
                  dlgHBoxLayout{ dlgLabel("Origin X:\t\t"); dlgStretch(1);  dlgLabel(itoa(u2mm(-minX)) + " mm"); }
                  dlgHBoxLayout{ dlgLabel("Origin Y:\t\t"); dlgStretch(1);  dlgLabel(itoa(u2mm(-minY)) + " mm"); }
                  dlgHBoxLayout{ dlgLabel("Width X:\t\t");  dlgStretch(1);  dlgLabel(itoa(u2mm(maxX-minX)) + " mm"); }
                  dlgHBoxLayout{ dlgLabel("Height Y:\t\t"); dlgStretch(1);  dlgLabel(itoa(u2mm(maxY-minY)) + " mm"); }
                }
                dlgGroup("Additional Offset") {
                  dlgHBoxLayout{ dlgLabel("Offset X:\t");         dlgRealEdit(offsetX, -10000, 10000);     dlgLabel("mm");} 
                  dlgHBoxLayout{ dlgLabel("Offset Y:\t");         dlgRealEdit(offsetY, -10000, 10000);     dlgLabel("mm");}             
                }
                dlgGroup("Fiducial marks"){
                  dlgCheckBox("Use fiducial marks for pcb calibration", useFiducials);
                }
                dlgGroup("Panel options"){
                  dlgHBoxLayout {
                    dlgCheckBox("Panelise",panelise);
                    dlgStretch(1);
                    dlgPushButton("Define") showPanelOptions();
                  }
                }
                dlgPushButton("Apply settings") {
                  dlgAccept();
                } 
                if(pnpStatsPartsError){
                  dlgLabel("Negative part coordinates are not supported, \nplease correct the offset!");
                }
                dlgStretch(1);
              }
            }
          }
          dlgTabPage("Feeder config") {
            dlgHBoxLayout {
              dlgListView(availableFeederHeadline, availableFeederList, selected, sorted);
              dlgVBoxLayout {
                dlgGroup("Feeder Config") {
                  dlgRadioButton("Local CSV", feederListMode);
                  dlgStringEdit(feederCSV); 
                  dlgRadioButton("Google spreadsheet", feederListMode);
                  dlgStringEdit(feederListUrl); 
                  dlgPushButton("Refresh feeder list") {
                    downloadFeederData();
                    dlgAccept();
                  }
                }
                dlgStretch(1);
              }
            }
          }
          dlgTabPage("Tray config") {
            dlgHBoxLayout {
              dlgListView(availableTrayHeadline, availableTrayList, selected, sorted);
              dlgVBoxLayout {
                dlgGroup("Tray Config") {
                  dlgRadioButton("Local CSV", trayListMode);
                  dlgStringEdit(trayCSV); 
                  dlgRadioButton("Google spreadsheet", trayListMode);
                  dlgStringEdit(trayListUrl); 
                  dlgPushButton("Refresh tray list") {
                    downloadTrayData();
                    dlgAccept();
                  }
                }
                dlgStretch(1);
              }
            }            
          }
          dlgTabPage("Feeders Used") {
            dlgListView("Feeder Number\tPart Name", usedFeederList, selected, sortedFeedersUsed);
          }
        }
        dlgVBoxLayout {
          dlgGroup("Statistics") { 
            dlgHBoxLayout{ dlgLabel("Parts total:\t\t");         dlgLabel(itoa(pnpStatsPartsTotal)); }
            dlgHBoxLayout{ dlgLabel("Parts to mount:\t\t");      dlgLabel(itoa(pnpStatsPartsOk));    }
            dlgHBoxLayout{ dlgLabel("Parts not assigned:\t\t");  dlgLabel(itoa(pnpStatsPartsNew));   }
            dlgHBoxLayout{ dlgLabel("Parts not mounted:\t\t");   dlgLabel(itoa(pnpStatsPartsDnp));   }
          }
          dlgGroup("Output") {
            dlgCheckBox("Top placement data", enableTop);
            dlgCheckBox("Bottom placement data", enableBottom);
            dlgGroup("Bottom flip") {
              dlgRadioButton("Flip vertical",   flipHorizontal);
              dlgRadioButton("Flip horizontal", flipHorizontal);
            }

            dlgPushButton("Save output file") {
              if(enableTop){
                writeOutputFile(0, "-top");
              }
              if(enableBottom){
                writeOutputFile(1, "-bot");
              }
              dlgAccept(-1);
            }           
          }
          dlgStretch(1);
        }
      }
    };

    //Write the config file
    configWrite();

    //If are done, abort
    if(dstatus == -1){break;}

    //If we don't abort, refresh config
    loadBoardInformation();
  }
  return 1;
}

if (!board) {
    //switches to the board and starts again
    exit ("EDIT .brd; RUN "+argv[0]);  
} else {

    showListOfDevices();
}
